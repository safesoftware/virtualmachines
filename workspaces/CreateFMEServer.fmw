FME workspace CreateFMEServer.fmw

Parameters:
- aws_connection = FME Virtual Machines IAM Amazon Web Services   # "Amazon Web Services" AWS Web Connection

Bookmark: Set Parameters
Note: We need the aws access key and aws secret access key from the web connection for use in later PythonCallers.
PythonCreator_AWS_Credentials
    NEW_ATTRIBUTES = AWS_ACCESS_KEY_ID AWS_SECRET_ACCESS_KEY
    PYTHONSOURCE_NEW:
      import fme
      import fmeobjects
      import collections

      from fmewebservices import FMETokenConnection  # noqa
      from fmegeneral.webservices import NamedConnectionManager

      def aws_credentials_from_conn_name(feature):
         # noinspection PyArgumentList
         named_connection = NamedConnectionManager().getNamedConnection(
             FME_MacroValues['aws_connection']
         )  # type: FMETokenConnection

         try:
             key_vals = named_connection.getKeyValues()
             key = key_vals.get("AWS_ACCESS_KEY", None)
             secret = key_vals.get("AWS_SECRET", None)
             feature.setAttribute("AWS_ACCESS_KEY_ID", key)
             feature.setAttribute("AWS_SECRET_ACCESS_KEY", secret)
         except Exception as e:
             feature.setAttribute("_exception", 'PythonCreator_AWS_Credentials: ' + repr(e))
    PYTHONSYMBOL = aws_credentials_from_conn_name
    -> FeatureReader [INITIATOR]
Note: Get settings from settings.json
FeatureReader
    ATTRIBUTES = JSONFeature,"git.username,git.repository,git.branch,aws.name_tag,aws.s3_bucket_name,aws.region_name,aws.vpc_cidr,aws.subnet_cidr{},ami.linux,ami.windows,flexnet.ec2type,flexnet.ec2size,flexnet.volumeSize,flexnet.securityGroup,fmeserver.ec2type,fmeserver.ec2size,fmeserver.volumeSize,fmeserver.securityGroup,fmeserver.docker-compose.yaml,fmeserver.vm.repository,fmeserver.vm.workspace,fmeserver.vm.server,fmeserver.vm.token,fme.ec2type,fme.ec2size,fme.volumeSize,fme.securityGroup,fme.timezone,fme.portForarding,fme.password,fme.installApps,fme.vm.instanceInitiatedShutdownBehavior,fme.vm.fromEmail,fme.vm.CCEmail,fme.vm.BCCEmail,web.repository,web.workspace,web.server,web.token,fme.vm.template.email{},fme.vm.template.rdp{},fme_geometry{0}"
    ATTR_ACCUM_MODE = Merge Initiator and Result
    ATTR_CONFLICT_RES = Use Result
    COMBINE_GEOM = Use Initiator
    DATASET = ../settings.json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> AttributeRemover
Note: clean up settings.json
AttributeRemover
    LIST_ATTRS = fme.vm.template.email{} fme.vm.template.rdp{} fme_geometry{}
    REMOVE_ATTRS = web.token,flexnet.ec2type,fme.timezone,fme.ec2size,fme.vm.fromEmail,fme.vm.BCCEmail,ami.windows,flexnet.volumeSize,flexnet.ec2size,fme.vm.CCEmail,fme.vm.template.email{0},flexnet.securityGroup,fme.installApps,fme.vm.template.rdp{0},fme.volumeSize,web.workspace,fme.ec2type,fme.portForarding,fme.vm.instanceInitiatedShutdownBehavior,web.server,fme.securityGroup,web.repository,fme.password
    -> AttributeCreator
Note: Create UserData
AttributeCreator
    ATTR_TABLE:
      SET_TO UserData = Content-Type: multipart/mixed; boundary="//"
        MIME-Version: 1.0

        --//
        Content-Type: text/cloud-config; charset="us-ascii"
        MIME-Version: 1.0
        Content-Transfer-Encoding: 7bit
        Content-Disposition: attachment; filename="cloud-config.txt"

        #cloud-config
        cloud_final_modules:
        - [scripts-user, always]

        --//
        Content-Type: text/x-shellscript; charset="us-ascii"
        MIME-Version: 1.0
        Content-Transfer-Encoding: 7bit
        Content-Disposition: attachment; filename="userdata.txt"

        #!/bin/bash

        yum -y update
        yum -y install redhat-lsb-core
        yum -y install git
        amazon-linux-extras install docker -y
        service docker start
        curl -L https://github.com/docker/compose/releases/download/1.22.0/docker-compose-$(uname -s)-$(uname -m) -o /usr/local/bin/docker-compose
        chmod +x /usr/local/bin/docker-compose

        cd /usr/local/bin
        wget @Value(fmeserver.docker-compose.yaml)

        sed -i '/- 80:8080/d' ./docker-compose.yaml
        export WEBPROTOCOL=http
        export EXTERNALPORT=80

        ./docker-compose up -d


        --//
    -> PythonCaller_Describe_decribe_images

Bookmark: Find the most recent Amazon Linux 2 AMI for this region
PythonCaller_Describe_decribe_images
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_images(
                  ExecutableUsers=[
                      'all',
                  ],
                  Filters=[
                      {
                          'Name': 'state',
                          'Values': [
                              'available',
                          ]
                      },
                      {
                          'Name': 'architecture',
                          'Values': [
                              'x86_64',
                          ]
                      },
                      {
                          'Name': 'image-type',
                          'Values': [
                              'machine',
                          ]
                      },
                      {
                          'Name': 'virtualization-type',
                          'Values': [
                              'hvm',
                          ]
                      },
                        {
                          'Name': 'description',
                          'Values': [
                              feature.getAttribute('ami.linux'),
                          ]
                      },
                      {
                          'Name': 'block-device-mapping.volume-type',
                          'Values': [
                              'gp2',
                          ]
                      },
                  ],
                  Owners=[
                      'amazon',
                  ],
              )
              feature.setAttribute("_response", json.dumps(response, default=str)) #https://stackoverflow.com/questions/11875770/how-to-overcome-datetime-datetime-not-json-serializable
          except Exception as e:
              feature.setAttribute("_exception", 'error in PythonCaller_Describe_decribe_images: ' + repr(e))
    PYTHONSYMBOL = AWSCall
    -> JSONFlattener_2
    -> AttributeExposer
JSONFlattener_2
    ERROR_LIST_ATTR = _json_error
    JSON_DOCUMENT = @Value(_response)
    NEW_ATTRIBUTES = Images{} Description ImageId
    READ_FROM_FILE = NO
    RECURSIVE = Yes
    -> ListExploder_images
ListExploder_images
    ATTR_ACCUM_MODE = Merge List Attributes
    ATTR_CONFLICT_RES = Use List Attribute Values
    INDEX_ATTR = _element_index
    LIST_ATTR = Images{}
    ELEMENTS -> Sorter

Bookmark: Get the most recent
Sorter
    SORT_PARM = Description ALPHA DESCENDING
    SORTED -> Sampler
Sampler
    RATE = 1
    SAMPLE_MODE = No
    SAMPLE_TYPE_LONG = First N Features
    SAMPLED -> PythonCaller_Describe_vpc

Bookmark: Find VPC
Note: Find VPC via Name tag
PythonCaller_Describe_vpc
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_vpcs(
                  Filters=[
                      {
                          'Name': 'tag:Name',
                          'Values': [
                              feature.getAttribute('aws.name_tag'),
                          ]
                      },
                  ],
              )
              feature.setAttribute("_response", json.dumps(response, default=str)) #https://stackoverflow.com/questions/11875770/how-to-overcome-datetime-datetime-not-json-serializable
          except Exception as e:
              feature.setAttribute("_exception", 'error in PythonCaller_Describe_vpc: ' + repr(e))
    PYTHONSYMBOL = AWSCall
    -> JSONFlattener_vpcs
    -> AttributeExposer
JSONFlattener_vpcs
    ERROR_LIST_ATTR = _json_error
    JSON_DOCUMENT = @Value(_response)
    READ_FROM_FILE = NO
    RECURSIVE = Yes
    -> AttributeRenamer
AttributeRenamer
    ATTR_TABLE = RENAME_SET_DEFAULT Vpcs{0}.VpcId > VpcId
    -> PythonCaller_Describe_subnet

Bookmark: Find Subnet
Note: Get list of subnets
PythonCaller_Describe_subnet
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_subnets(
                  Filters=[
                      {
                          'Name': 'vpc-id',
                          'Values': [
                              feature.getAttribute('VpcId'),
                          ]
                      },
                      {
                          'Name': 'state',
                          'Values': [
                              'available',
                          ]
                      },
                  ],
              )
              feature.setAttribute("_response", json.dumps(response, default=str)) #https://stackoverflow.com/questions/11875770/how-to-overcome-datetime-datetime-not-json-serializable
          except Exception as e:
              feature.setAttribute("_exception", 'error in PythonCaller_Describe_subnet: ' + repr(e))
    PYTHONSYMBOL = AWSCall
    -> JSONFlattener_subnet
    -> AttributeExposer
JSONFlattener_subnet
    ERROR_LIST_ATTR = _json_error
    JSON_DOCUMENT = @Value(_response)
    NEW_ATTRIBUTES = Subnets{} State SubnetId
    READ_FROM_FILE = NO
    RECURSIVE = Yes
    -> ListExploder
ListExploder
    ATTR_ACCUM_MODE = Merge List Attributes
    ATTR_CONFLICT_RES = Use List Attribute Values
    INDEX_ATTR = _element_index
    LIST_ATTR = Subnets{}
    ELEMENTS -> Sampler_subnet
Note: We only need one
Sampler_subnet
    RATE = 1
    SAMPLE_MODE = No
    SAMPLE_TYPE_LONG = First N Features
    SAMPLED -> PythonCaller_Describe_security_groups

Bookmark: Find Security Group
Note: Find the security groups
PythonCaller_Describe_security_groups
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_security_groups(
                  Filters=[
                      {
                          'Name': 'vpc-id',
                          'Values': [
                              feature.getAttribute('VpcId'),
                          ]
                      },
                      {
                          'Name': 'group-name',
                          'Values': [
                              feature.getAttribute('fmeserver.securityGroup'),
                          ]
                      },
                  ],

              )
              feature.setAttribute("_response", json.dumps(response, default=str)) #https://stackoverflow.com/questions/11875770/how-to-overcome-datetime-datetime-not-json-serializable
          except Exception as e:
              feature.setAttribute("_exception", 'error in PythonCaller_Describe_security_groups: ' + repr(e))
    PYTHONSYMBOL = AWSCall
    -> JSONFlattener_security
    -> AttributeExposer
JSONFlattener_security
    ERROR_LIST_ATTR = _json_error
    JSON_DOCUMENT = @Value(_response)
    NEW_ATTRIBUTES = SecurityGroups{} GroupId GroupName
    READ_FROM_FILE = NO
    RECURSIVE = Yes
    -> AttributeRenamer_GroupId
AttributeRenamer_GroupId
    ATTR_TABLE = RENAME_SET_DEFAULT SecurityGroups{0}.GroupId > GroupId
    -> PythonCaller_run_instances

Bookmark: Start License Server machine
PythonCaller_run_instances
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.run_instances(
                  ImageId= feature.getAttribute('ImageId'),
                  InstanceType= feature.getAttribute('fmeserver.ec2type') + '.' + feature.getAttribute('fmeserver.ec2size'),
                  SubnetId= feature.getAttribute('SubnetId'),
                  MinCount= 1, MaxCount= 1,
                  DisableApiTermination=True,
                  UserData=feature.getAttribute('UserData'),
                  BlockDeviceMappings=[
                      {
                          'DeviceName': '/dev/xvda',
                          'Ebs': {
                              'DeleteOnTermination': True,
                              'VolumeSize': feature.getAttribute('fmeserver.volumeSize'),
                              'VolumeType': 'gp2',
                          },
                      },
                  ],
                  SecurityGroupIds=[
                          feature.getAttribute('GroupId'),
                      ],
                  TagSpecifications=[
                      {
                          'ResourceType': 'instance',
                          'Tags': [
                                          {'Key': 'Name', 'Value': feature.getAttribute('aws.name_tag') + ' FME Server'},
                                   ]
                       },
                   ],

              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener
    -> AttributeExposer
JSONFlattener
    ERROR_LIST_ATTR = _json_error
    JSON_DOCUMENT = @Value(_response)
    NEW_ATTRIBUTES = Instances{0}.NetworkInterfaces{0}.MacAddress
    READ_FROM_FILE = NO
    RECURSIVE = Yes

Bookmark: Error in PythonCaller
AttributeExposer
    ATTR_LIST = _exception
    -> Tester_has_exception
Tester_has_exception
    BOOL_OP = OR
    TEST_CLAUSE = TEST _exception ATTRIBUTE_HAS_A_VALUE ""
    TEST_MODE = TEST
    PASSED -> Terminator_exception
Terminator_exception
    MESSAGE = Translation Terminated. @Value(_exception)
