FME workspace QuickSetup.fmw

Parameters:
- aws_connection = FME Virtual Machines IAM Amazon Web Services   # "Amazon Web Services" AWS Web Connection

Creator
    GEOMTYPE = Geometry Object
    NUM = 1
    CREATED -> WorkspaceRunner_CreateVPC
Note: Create your VPC
WorkspaceRunner_CreateVPC
    BLOCKING = Yes
    WORKSPACE_FILE = CreateVPC.fmw
    SUCCEEDED -> WorkspaceRunner_CreateLicenseServer
Note: Your license server. It will only work with machines that are in the same VPC. Be sure to follow the instructions in LicenseServerInfo.txt, delete the serial number from safe.lic and then push the edited safe.lic to GitHub.
Note: Create your FlexNet license server
WorkspaceRunner_CreateLicenseServer
    BLOCKING = Yes
    WORKSPACE_FILE = ./CreateLicenseServer.fmw
    SUCCEEDED -> WorkspaceRunner_InitialMachineCreator
Note: The Template machine created will shut-down automatically when it is done installing everything. / That will take around 1 hour, but might be as fast as 30 minutes. / You should then log in to ensure that everything went according to plan, and then license FME. / Review the PostCreationSteps.md file for finishing touches.
Note: Create your initial training machine
WorkspaceRunner_InitialMachineCreator
    BLOCKING = Yes
    WORKSPACE_FILE = ./InitialMachineCreator.fmw
    SUCCEEDED -> WorkspaceRunner_CreateFMEServer
Note: Be sure to log in, license FME Server, and change the Admin password. This is where we will publish VMCreator.fmw
Note: Create your FME Server
WorkspaceRunner_CreateFMEServer
    BLOCKING = Yes
    WORKSPACE_FILE = $(FME_MF_DIR)CreateFMEServer.fmw
Note: This is only here to make it easier to edit the Web Connection. / Make sure to configure the Amazon Web Services web connection
PythonCreator_AWS_Credentials
    NEW_ATTRIBUTES = AWS_ACCESS_KEY_ID AWS_SECRET_ACCESS_KEY
    PYTHONSOURCE_NEW:
      import fme
      import fmeobjects
      import collections

      from fmewebservices import FMETokenConnection  # noqa
      from fmegeneral.webservices import NamedConnectionManager

      def aws_credentials_from_conn_name(feature):
         # noinspection PyArgumentList
         named_connection = NamedConnectionManager().getNamedConnection(
             FME_MacroValues['aws_connection']
         )  # type: FMETokenConnection

         try:
             key_vals = named_connection.getKeyValues()
             key = key_vals.get("AWS_ACCESS_KEY", None)
             secret = key_vals.get("AWS_SECRET", None)
             feature.setAttribute("AWS_ACCESS_KEY_ID", key)
             feature.setAttribute("AWS_SECRET_ACCESS_KEY", secret)
         except Exception as e:
             feature.setAttribute("_exception", 'PythonCreator_AWS_Credentials: ' + repr(e))
    PYTHONSYMBOL = aws_credentials_from_conn_name
